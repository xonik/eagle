string file_name;
string project_path;

string brd_top_suffix = "-brd-top";
string brd_bottom_suffix = "-brd-bottom";
string sch_suffix = "-sch";
string pac_suffix = "-pac";
string dev_suffix = "-dev";
string sym_suffix = "-sym";

int    sheetprint_from;
int    sheetprint_to;
int    lastsheet = 0;
string actualsheet;
int    sheetprint = 0;     // 0 = All, 1 = From To, 2 = Actual

// Board top or package layers
int topLayersLength = 7;
int topLayers[] = {21, 17, 18, 20, 25, 51, 1};

// Board bottom layers
int bottomLayersLength = 7;
int bottomLayers[] = {17, 18, 20, 22, 26, 52, 16};

// Other layers, need to change this
int ln = 7;
int exp_Layers[] = {91, 94, 95, 96, 97};

int lVisible[];
int useLayer[];

// Accumulated command to execute
string cmd = "";
string s;

// *** functions ***
void commandPrint(string name_suffix) {
  string h;
  sprintf(h, "EXPORT IMAGE '%s%s%s' %s %d;\n", file_name, name_suffix, ".png", "", 600);
  cmd += h;
  return;
}

void exportBoard(int boardView, string suffix) {
  // arrays cannot be passed as function parameters so we do it this way instead
  // arbitrary number of elements just to make room for whatever we copy
  int layers[] = {0,0,0,0,0,0,0,0,0,0,0,0,0,0,0,0,0,0,0,0,0,0,0};
  int layersLength;
  int l;
  if(boardView == 0 || boardView == 1) {
    layersLength = topLayersLength;
    for(int l = 0; l<layersLength; l++){
       layers[l] = topLayers[l];
    }
  } else {
    layersLength = bottomLayersLength;
    for(int l = 0; l<layersLength; l++){
       layers[l] = bottomLayers[l];
    }
  }

  cmd += "SET DISPLAY_MODE REAL;\n";
  cmd += "RATSNEST;\n";
  cmd += "DISPLAY NONE ";

  for (int x = 0; x < layersLength; x++) {
    int num = layers[x];
    if (num < 90 || num > 100) {
      if (useLayer[num]) {
        sprintf(s, " %d", num);
        cmd += s;
        if(num == 21) cmd += " -23 -25 -27 -51";
        if(num == 22) cmd += " -24 -26 -28 -52";
        //n++;
      }
    }
  }
  cmd += ";\n";
  commandPrint(suffix);
}

void exportSchematic() {
  cmd += "DISPLAY NONE ";
  for (int x = 0; x < ln; x++) {
    int num = exp_Layers[x];
    if (useLayer[num]) {
      if (num >= 90) {
        sprintf(s, " %d", exp_Layers[x]);
        cmd += s;
      }
    }
  }
  cmd += ";\n";
  string sh;
  string shn;
  if (schematic) {  // 2008-06-23
    switch (sheetprint) {
      case 0 : schematic(S) {
               S.sheets(SH) {
                 sprintf(sh, "EDIT '.s%d';\n", SH.number);
                 cmd += sh;
                 sprintf(shn, "_s%d", SH.number);
                 // TODO filenames here
                 commandPrint(shn);
               }
             }
             break;

      case 1 : for (int prn = sheetprint_from; prn <= sheetprint_to; prn++) {
               sprintf(sh, "EDIT '.s%d';\n", prn);
               cmd += sh;
               sprintf(shn, "_s%d", prn);
               commandPrint(shn);
             }
             break;

      case 2 : sprintf(sh, "EDIT '.s%s';\n", actualsheet);
             cmd += sh;
             sprintf(shn, "_s%s", actualsheet);
             commandPrint(shn);
             break;
    }
  }
  else if (deviceset) commandPrint(dev_suffix);
  else if (symbol) commandPrint(sym_suffix);
}

void restoreBoardView() {
  cmd += "DISPLAY ";
  for(int l = 1; l < 90; l++) {
    if (useLayer[l]) {
      if (lVisible[l]) {
        sprintf(s, " %d", l);
        cmd += s;
      }
      else {
        sprintf(s, " -%d", l);
        cmd += s;
      }
    }
  }
  for(l = 100; l < 256; l++) {
    if (useLayer[l]) {
      if (lVisible[l]) {
        sprintf(s, " %d", l);
        cmd += s;
      }
      else {
        sprintf(s, " -%d", l);
        cmd += s;
      }
    }
  }
  cmd += ";\n";
}

void restoreSchematicView(){
  cmd += "DISPLAY ";
  for(int l = 91; l < 256; l++) {
    if (useLayer[l]) {
      if (lVisible[l]) {
        sprintf(s, " %d", l);
        cmd += s;
      }
      else {
        sprintf(s, " -%d", l);
        cmd += s;
      }
    }
  }
  cmd += ";\n";
  if(schematic) {      // 2008-06-23 alf@cadsoft.de
    sprintf(s, "EDIT '.s%s';\n", actualsheet);
    cmd += s;
  }
}

void saveBoardView(){
  board(B) {
    file_name = filesetext(B.name, "");
    project_path = filedir(B.name);
    B.layers(L) {
      lVisible[L.number] = L.visible;
      useLayer[L.number] = L.used;
    }
  }
}

void saveSchematicView(){
  schematic(S) {
    file_name = filesetext(S.name, "");
    project_path = filedir(S.name);
    if (sheet) sheet(SH) sprintf(actualsheet, "%d", SH.number);
    S.sheets(SH) {
      lastsheet = SH.number;
    }
    S.layers(L) {
      lVisible[L.number] = L.visible;
      useLayer[L.number] = L.used;
    }
  }
  sheetprint_to = lastsheet;
}

void saveOtherView() {
  library(LBR) {
    if (package) {
      package(P) {
        file_name = P.name;
        project_path = filedir(P.name);
      }
    } else if(symbol) {
      symbol(SYM) {
        file_name = SYM.name;
        project_path = filedir(SYM.name);
      }
    } else if (deviceset) {
      deviceset(DEV) {
        file_name = DEV.name;
        project_path = filedir(DEV.name);
      }
    }
    LBR.layers(L) {
      lVisible[L.number] = L.visible;
      useLayer[L.number] = L.used;
    }
  }
}

void gitAdd(string file) {
  sprintf(s, "cd %s && git add %s > /tmp/out.txt 2> /tmp/err.txt", project_path, file);
  system(s);
}

// main
// https://community.element14.com/products/eagle/f/eagle-user-support-english/16690/running-cam-from-ulp
//int i = system("p");

// Eagle builtin constants: http://web.mit.edu/xavid/arch/i386_rhel4/help/228.htm
// Åpne schematic? https://community.element14.com/products/eagle/f/eagle-user-support-english/4756/path-to-current-schematic-in-ulp

// RUN ULP from terminal: https://electronics.stackexchange.com/questions/269623/is-it-possible-to-run-eaglecads-drc-from-a-terminal-and-pipe-the-error-list-to

if (schematic) {
  saveSchematicView();

  // remove all current images to prevent "overwrite" dialog
  // TODO: Filenames!
  sprintf(s, "rm -f \"%s_sch.png\" > /tmp/out.txt 2> /tmp/err.txt", file_name);
  int i = system(s);

} else if (board) {
  saveBoardView();

  // remove all current images to prevent "overwrite" dialog
  sprintf(s, "rm -f \"%s%s.png\" > /tmp/out.txt 2> /tmp/err.txt", file_name, brd_top_suffix);
  system(s);
  sprintf(s, "rm -f \"%s%s.png\" > /tmp/out.txt 2> /tmp/err.txt", file_name, brd_bottom_suffix);
  system(s);
} else if (package || symbol || deviceset) {
  saveOtherView();
  // TODO: Remove other
} else {
  dlgMessageBox("Start this ULP in a SCH, BRD, DEV, PAC or SYM:", "OK");
  exit(-1);
}

// REAL SCRIPT STARTS HERE
if(board) {
  exportBoard(1, brd_top_suffix);
  exportBoard(2, brd_bottom_suffix);
  sprintf(s, "\"%s%s\" > /tmp/out.txt 2> /tmp/err.txt", file_name, ".brd");
  gitAdd(s);
  // TODO: Virker ikke fordi de kjører for tidlig, før exit.
} else if(package) {
  exportBoard(0, pac_suffix);
} else if(schematic || deviceset || symbol) {
  exportSchematic();
}

if(board || package) {
  restoreBoardView();
} else if(schematic || deviceset || symbol) { // 2008-06-23
  restoreSchematicView();
}

exit (cmd);
