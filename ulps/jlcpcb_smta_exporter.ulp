/*

Copyright 2019 OXullo Intersecans <x@brainrapers.org>

Permission is hereby granted, free of charge, to any person obtaining a copy of this software and associated documentation files (the "Software"), to deal in the Software without restriction, including without limitation the rights to use, copy, modify, merge, publish, distribute, sublicense, and/or sell copies of the Software, and to permit persons to whom the Software is furnished to do so, subject to the following conditions:

The above copyright notice and this permission notice shall be included in all copies or substantial portions of the Software.

THE SOFTWARE IS PROVIDED "AS IS", WITHOUT WARRANTY OF ANY KIND, EXPRESS OR IMPLIED, INCLUDING BUT NOT LIMITED TO THE WARRANTIES OF MERCHANTABILITY, FITNESS FOR A PARTICULAR PURPOSE AND NONINFRINGEMENT. IN NO EVENT SHALL THE AUTHORS OR COPYRIGHT HOLDERS BE LIABLE FOR ANY CLAIM, DAMAGES OR OTHER LIABILITY, WHETHER IN AN ACTION OF CONTRACT, TORT OR OTHERWISE, ARISING FROM, OUT OF OR IN CONNECTION WITH THE SOFTWARE OR THE USE OR OTHER DEALINGS IN THE SOFTWARE.

*/

// Note: the following eagle-bundled ULPs have been used as a guidance:
// * mountsmd.ulp
// * bom.ulp
// * cmd-change-swap-layer.ulp
// * centroid-screamingcircuits-smd.ulp


#usage "<b>JLCPCB BOM/CPL files generator</b>\n"
       "<p>"
       "Generates BOM and CPL files for JLCPCB SMT assembly service"
       "https://jlcpcb.com/smt-assembly"
       "<p>"
       "Run the ULP from the board editor"
       "<p>"
       "<author>Author: OXullo Intersecans x@brainrapers.org</author>"


int layer_id_map[] = { 1, 16 };
UL_ELEMENT selected_elements[];
string layer_name_map[] = { "Top", "Bottom" };

if (board) board(B) {

	string txt;
    int layer_choice = 0;

    dlgDialog("Layer selection") {
	    dlgGroup("Export layer") {
	    	dlgRadioButton("&Top", layer_choice);
	    	dlgRadioButton("&Bottom", layer_choice);
	    }
        dlgPushButton("OK") dlgAccept();
    };

	string output_dir = dlgDirectory("Export files to", filedir(B.name));

	if (output_dir == "") {
		exit(0);
	}

	int element_count = 0;

	B.elements(E) if (E.populate) {
		E.package.contacts(C) {
      // Fixes by joakim: Removed check to force printing of non-smd components
			//if (C.smd && C.smd.layer == layer_id_map[layer_choice]) {
				selected_elements[element_count++] = E;
				break;
			//}
		}
	}

	string base_path = (output_dir + "/" +
		strsub(filename(B.name), 0, strlen(filename(B.name)) - 4) +
		"_" + strlwr(layer_name_map[layer_choice]));

	string cpl_filename = base_path + "_cpl.csv";
	string bom_filename = base_path + "_bom.csv";

	output(cpl_filename) {
		printf("Designator,Mid X,Mid Y,Layer,Rotation\n");

		for (int i = 0 ; i < element_count ; i++) {
			UL_ELEMENT E = selected_elements[i];

        	printf("%s,%5.2f,%5.2f,%s,%.1f\n",
        		E.name, u2mm(E.x), u2mm(E.y),
        		layer_name_map[layer_choice],
		        E.angle);
		}
	}

	output(bom_filename) {
		int i;
		int indexes[];
		numeric string values[];

		for (i=0 ; i < element_count ; i++) {
			indexes[i] = i;
			values[i] = selected_elements[i].value;
		}
		sort(element_count, indexes, values);
		printf("Comment,Designator,Footprint,LCSC Part #\n");

		string current_value = "";
		string current_footprint = "";
		string current_lscpart = "";
		string designators = "";

		for (i = 0 ; i < element_count ; i++) {
			UL_ELEMENT E = selected_elements[indexes[i]];

      string partValue = E.value;
      if(partValue == ""){
        partValue = E.footprint.name;
      }

      // If the current value or footprint has changed, print a bom line with the
      // contents found this far.
			if (
        (current_value != "" &&
          (partValue != current_value || E.footprint.name != current_footprint)
        )
      ) {
				printf("%s,%s,%s,%s\n", current_value, designators, current_footprint, current_lscpart);
				designators = "";
			}

			if (designators != "") {
				designators += " ";
			}
			designators += E.name;
			current_value = partValue;
			current_footprint = E.footprint.name;
			current_lscpart = "";
      //printf("%s,%s,%s,%s\n", current_value, designators, current_footprint, current_lscpart);

			E.attributes(A) {
				if (A.name == "LCSC_PART") {
					current_lscpart = A.value;
				}
			}

      // The last group is not printed automatically as there no next part and thus
      // no difference to detect. We also need to do it after the last part has been
      // added to designators to include the very last part of the bom.
      if (
        i == element_count - 1
      ) {
				printf("%s,%s,%s,%s\n", current_value, designators, current_footprint, current_lscpart);
				designators = "";
			}
		}
	}

  dlgMessageBox("BOM and CPL files have been exported to: " + output_dir, "OK");

} else {
  dlgMessageBox("Run this ULP from a Board", "OK");
  exit (0);
}
